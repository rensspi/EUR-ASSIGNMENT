FME workspace LastChangedWriter.fmw

Parameters:
- PARQUETFOLDER = K:\CentraalDatamanagement\PDC\01_WIP\01_Algemeen\X_000002_DatakwaliteitBaseline\DAMO_H_parquet   # parquetfolder
- output_csv_folder = K:\CentraalDatamanagement\PDC\01_WIP\01_Algemeen\X_000002_DatakwaliteitBaseline\70_Resultaten   # output csv folder

PythonCreator
    NEW_ATTRIBUTES = parquet_file char(200)
    PYTHONSOURCE_NEW:
      import fme
      from fme import BaseTransformer
      import fmeobjects
      import glob


      class FeatureCreator(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def input(self, feature: fmeobjects.FMEFeature):
              """This method is called once by FME to initiate feature creation.
              Any number of features can be created and emitted by the self.pyoutput() method.
              The initial feature argument is a placeholder and can be ignored.
              """

              input_folder = FME_MacroValues['PARQUETFOLDER']
              parquets = glob.glob("{}\*.parquet".format(input_folder))

              for i in parquets:
                  newFeature = fmeobjects.FMEFeature()
                  newFeature.setAttribute("parquet_file", i)
                  self.pyoutput(newFeature)

          def close(self):
              """This method is called at the end of the class."""
              pass
    PYTHONSYMBOL = FeatureCreator
    -> Sampler
Sampler
    MODE = ORIGINAL
    RATE = 5
    SAMPLE_TYPE_MULTIPLIER = -1
    SAMPLE_MODE = No
    SAMPLE_TYPE_LONG = First N Features
    SAMPLED -> FeatureReader [INITIATOR]
FeatureReader
    ATTRS_TO_EXPOSE = fme_basename
    ATTR_ACCUM_MODE = Only Use Result
    CLIP_TO_ENVELOPE = NO
    COMBINE_GEOM = Use Result
    DATASET = @Value(parquet_file)
    FORMAT = GEOPARQUET
    GEOPARQUET_SUPPORT_LISTS = yes
    INITIATOR_FIRST_OUTPUT = default
    INTERACT = NONE
    ORDER_RESULTS = No
    OUTPUT_ADD_SCHEMA_ATTRIBUTES = NO
    OUTPUT_FEATURES_DISPLAY = Schema and Data Features
    <SCHEMA> -> SchemaMapper
    <OTHER> -> AttributeExposer
AttributeExposer
    ATTR_TABLE = GDB_FROM_DATE,,OBJECTID,
    -> DateTimeConverter
DateTimeConverter
    DATETIME_ATTR = GDB_FROM_DATE
    IN_FORMAT = FME
    OUT_FORMAT = %Y-%m-%d %H:%M:%S
    PASSTHROUGH = NO
    REPAIR_INPUT = YES
    -> PythonCaller
PythonCaller
    GROUP_BY = OBJECTID
    PYTHONSOURCE:
      import fme
      from fme import BaseTransformer
      import fmeobjects
      from collections import defaultdict
      from datetime import datetime
      import csv
      import os

      class FeatureProcessor(BaseTransformer):
          def __init__(self):
              self.feature_groups = defaultdict(list)
              self.output_folder = fme.macroValues["output_csv_folder"]  # Retrieve the user parameter for the output folder

          def input(self, feature: fmeobjects.FMEFeature):
              object_id = feature.getAttribute("OBJECTID")
              self.feature_groups[object_id].append(feature)

          def close(self):
              for object_id, features in self.feature_groups.items():
                  # Sort features by GDB_FROM_DATE in ascending order
                  features.sort(key=lambda f: datetime.strptime(f.getAttribute("GDB_FROM_DATE"), "%Y-%m-%d %H:%M:%S"))

                  # Get the feature with the latest GDB_FROM_DATE
                  latest_feature = features[-1]

                  # Create a dictionary to store the earliest GDB_FROM_DATE for each attribute
                  last_changed_dates = {}

                  for feature in features:
                      for attr in feature.getAllAttributeNames():
                          if attr not in ["OBJECTID", "GDB_FROM_DATE"]:
                              if feature.getAttribute(attr) == latest_feature.getAttribute(attr):
                                  if attr not in last_changed_dates:
                                      last_changed_dates[attr] = feature.getAttribute("GDB_FROM_DATE")

                  # Add the new attributes to the latest feature
                  for attr, date in last_changed_dates.items():
                      latest_feature.setAttribute(f"{attr}_last_changed", date)

                  # Determine the basename for the CSV file
                  basename = latest_feature.getAttribute("fme_basename")
                  if not basename:
                      basename = "default"

                  # Prepare the CSV file path in the specified output folder
                  csv_file_path = os.path.join(self.output_folder, f"{basename}.csv")

                  # Ensure the output folder exists
                  os.makedirs(self.output_folder, exist_ok=True)

                  # Write only the attributes with the suffix "_last_changed" to the CSV file
                  with open(csv_file_path, mode="a", newline="", encoding="utf-8") as csv_file:
                      writer = csv.writer(csv_file)

                      # Filter attributes with the suffix "_last_changed"
                      last_changed_attrs = [attr for attr in latest_feature.getAllAttributeNames() if attr.endswith("_last_changed")]

                      # Write header if the file is empty
                      if os.stat(csv_file_path).st_size == 0:
                          writer.writerow(last_changed_attrs)

                      # Write the feature attributes
                      row = [latest_feature.getAttribute(attr) for attr in last_changed_attrs]
                      writer.writerow(row)

                  # Output the latest feature with the new attributes
                  self.pyoutput(latest_feature, output_tag="PYOUTPUT")
    PYTHONSYMBOL = FeatureProcessor
    -> AttributeCreator
AttributeCreator
    ATTR_TABLE = SET_TO output_name (buffer) = @Value(fme_basename)_lastedited
    -> FeatureWriter [Output]
    -> ListBuilder
ListBuilder
    GROUP_BY = OBJECTID
    LIST_NAME = _list
    -> ListConcatenator
ListConcatenator
    DROP_EMPTY_PARTS = No
    SEP = ,
    VAL_ATTR = _concatenated
    -> ListExploder
ListExploder
    ATTR_ACCUM_MODE = Merge List Attributes
    ATTR_CONFLICT_RES_LOOKUP = INCOMING_IF_CONFLICT
    INDEX_ATTR = 0
    LIST_ATTR = _list{}
    ATTR_CONFLICT_RES = Use List Attribute Values
FeatureWriter
    DATASET = K:\CentraalDatamanagement\PDC\01_WIP\01_Algemeen\X_000002_DatakwaliteitBaseline\DAMO_H_parquet\Output
    DATASET_ATTR = _dataset
    FEATURE_TYPE_LIST_ATTR = _feature_types
    FORMAT = GEOPARQUET
    GEOPARQUET_COMPRESSION = UNCOMPRESSED
    GEOPARQUET_COORDINATE_SYSTEM_GRANULARITY = FEATURE_TYPE
    GEOPARQUET_VERSION = 2.0
    TOTAL_FEATURES_WRITTEN_ATTR = _total_features_written
SchemaMapper
    FORMAT = CSV2
    ROW_ID_ATTR = _schemamapper_row_ids
