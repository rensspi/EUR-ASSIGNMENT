FME workspace TimeChecker.fmw
Title: TimeChecker
Description: Deze workspace is gemaakt als onderdeel van de opdracht van Rens en Maarten voor hun opleiding Data en AI Engineering. De workspace leest history tables in parquetvorm in en schrijft een csv weg. In deze csv zijn de waarden vervangen door het moment waarop deze het laatst zijn gewijzigd. Het script is zo gemaakt dat het met een FME Jobsubmitter aangeroepen kan worden.
History: 23-12-2025,Maarten,Aangemaakt

Parameters:
- output_csv_folder = K:\CentraalDatamanagement\PDC\01_WIP\01_Algemeen\X_000002_DatakwaliteitBaseline\70_Resultaten   # output csv folder
- parquet_file =   # "" Select a parquet file

Note: AttributeExposer [AttributeExposer] / Attributes To Expose: AttributeTypeGDB_FROM_DATEOBJECTID
AttributeExposer
    ATTR_TABLE = GDB_FROM_DATE,,OBJECTID,
    -> DateTimeConverter
Note: DateTimeConverter [DateTimeConverter] / General: / Datetime Attributes: GDB_FROM_DATE / Input Format: FME / Output Format: %Y-%m-%d %H:%M:%S / Repair Overflow: Yes / Passthrough Nulls, Empties, or Missing: No / Preview: / Preview Data: / Input Data: <not set>
DateTimeConverter
    DATETIME_ATTR = GDB_FROM_DATE
    IN_FORMAT = FME
    OUT_FORMAT = %Y-%m-%d %H:%M:%S
    PASSTHROUGH = NO
    REPAIR_INPUT = YES
    -> PythonCaller
Note: PythonCaller: / import fme / from fme import BaseTransformer / import fmeobjects / from collections import defaultdict / from datetime import datetime / import csv / import os / class FeatureProcessor(BaseTransformer): / def __init__(self): / self.feature_groups = defaultdict(list) / self.output_folder = fme.macroValues["output_csv_folder"] # Retrieve the user parameter for the output folder / def input(self, feature: fmeobjects.FMEFeature): / object_id = feature.getAttribute("OBJECTID") / self.feature_groups[object_id].append(feature) / def close(self): / for object_id, features in self.feature_groups.items(): / # Sort features by GDB_FROM_DATE in ascending order / features.sort(key=lambda f: datetime.strptime(f.getAttribute("GDB_FROM_DATE"), "%Y-%m-%d %H:%M:%S")) / # Get the feature with the latest GDB_FROM_DATE / latest_feature = features[-1] / # Create a dictionary to store the earliest GDB_FROM_DATE for each attribute / last_changed_dates = {} / for feature in features: / for attr in feature.getAllAttributeNames(): / if attr not in ["OBJECTID", "GDB_FROM_DATE"]: / if feature.getAttribute(attr) == latest_feature.getAttribute(attr): / if attr not in last_changed_dates: / last_changed_dates[attr] = feature.getAttribute("GDB_FROM_DATE") / # Add the new attributes to the latest feature / for attr, date in last_changed_dates.items(): / latest_feature.setAttribute(f"{attr}_last_changed", date) / # Determine the basename for the CSV file / basename = latest_feature.getAttribute("fme_basename") / if not basename: / basename = "default" / # Prepare the CSV file path in the specified output folder / csv_file_path = os.path.join(self.output_folder, f"{basename}.csv") / # Ensure the output folder exists / os.makedirs(self.output_folder, exist_ok=True) / # Write the attributes including OBJECTID and those with the suffix "_last_changed" to the CSV file / with open(csv_file_path, mode="a", newline="", encoding="utf-8") as csv_file: / writer = csv.writer(csv_file) / # Include OBJECTID and filter attributes with the suffix "_last_changed" / last_changed_attrs = ["OBJECTID"] + [attr for attr in latest_feature.getAllAttributeNames() if attr.endswith("_last_changed")] / # Write header if the file is empty / if os.stat(csv_file_path).st_size == 0: / writer.writerow(last_changed_attrs) / # Write the feature attributes / row = [latest_feature.getAttribute(attr) for attr in last_changed_attrs] / writer.writerow(row) / # Output the latest feature with the new attributes / self.pyoutput(latest_feature, output_tag="PYOUTPUT")
PythonCaller
    GROUP_BY = OBJECTID
    PYTHONSOURCE:
      import fme
      from fme import BaseTransformer
      import fmeobjects
      from collections import defaultdict
      from datetime import datetime
      import csv
      import os

      class FeatureProcessor(BaseTransformer):
          def __init__(self):
              self.feature_groups = defaultdict(list)
              self.output_folder = fme.macroValues["output_csv_folder"]  # Retrieve the user parameter for the output folder

          def input(self, feature: fmeobjects.FMEFeature):
              object_id = feature.getAttribute("OBJECTID")
              self.feature_groups[object_id].append(feature)

          def close(self):
              for object_id, features in self.feature_groups.items():
                  # Sort features by GDB_FROM_DATE in ascending order
                  features.sort(key=lambda f: datetime.strptime(f.getAttribute("GDB_FROM_DATE"), "%Y-%m-%d %H:%M:%S"))

                  # Get the feature with the latest GDB_FROM_DATE
                  latest_feature = features[-1]

                  # Create a dictionary to store the earliest GDB_FROM_DATE for each attribute
                  last_changed_dates = {}

                  for feature in features:
                      for attr in feature.getAllAttributeNames():
                          if attr not in ["OBJECTID", "GDB_FROM_DATE"]:
                              if feature.getAttribute(attr) == latest_feature.getAttribute(attr):
                                  if attr not in last_changed_dates:
                                      last_changed_dates[attr] = feature.getAttribute("GDB_FROM_DATE")

                  # Add the new attributes to the latest feature
                  for attr, date in last_changed_dates.items():
                      latest_feature.setAttribute(f"{attr}_last_changed", date)

                  # Determine the basename for the CSV file
                  basename = latest_feature.getAttribute("fme_basename")
                  if not basename:
                      basename = "default"

                  # Prepare the CSV file path in the specified output folder
                  csv_file_path = os.path.join(self.output_folder, f"{basename}.csv")

                  # Ensure the output folder exists
                  os.makedirs(self.output_folder, exist_ok=True)

                  # Write the attributes including OBJECTID and those with the suffix "_last_changed" to the CSV file
                  with open(csv_file_path, mode="a", newline="", encoding="utf-8") as csv_file:
                      writer = csv.writer(csv_file)

                      # Include OBJECTID and filter attributes with the suffix "_last_changed"
                      last_changed_attrs = ["OBJECTID"] + [attr for attr in latest_feature.getAllAttributeNames() if attr.endswith("_last_changed")]

                      # Write header if the file is empty
                      if os.stat(csv_file_path).st_size == 0:
                          writer.writerow(last_changed_attrs)

                      # Write the feature attributes
                      row = [latest_feature.getAttribute(attr) for attr in last_changed_attrs]
                      writer.writerow(row)

                  # Output the latest feature with the new attributes
                  self.pyoutput(latest_feature, output_tag="PYOUTPUT")
    PYTHONSYMBOL = FeatureProcessor

Bookmark: Inlezen van parquet-dataset
Creator
    GEOMTYPE = Geometry Object
    NUM = 1
    CREATED -> FeatureReader [INITIATOR]
FeatureReader
    ATTRS_TO_EXPOSE = fme_basename
    ATTR_ACCUM_MODE = Only Use Result
    CLIP_TO_ENVELOPE = NO
    COMBINE_GEOM = Use Result
    DATASET = $(parquet_file)
    FORMAT = GEOPARQUET
    GEOPARQUET_SUPPORT_LISTS = yes
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer
