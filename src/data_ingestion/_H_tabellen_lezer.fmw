FME workspace _H_tabellen_lezer.fmw
Title: _H-tabellen lezer
Description: Dit script is gemaakt om _H-tabellen uit te lezen en weg te schrijven naar een file geodatabase. Dit was nodig in het kader van een opdracht om tot een baseline datakwaliteit te komen.
History: 27-10-2025,Maarten Baas,Script aangemaakt

Parameters:
- SDE_bestand = L:\Project9\FME\FME_Centraal\Connecties\ESRI\Test\DAMOTST_raadpleger.sde   # SDE met archived feature classes
- OracleConnectie = DAMOPRD_Oracle   # FAMILY:Oracle Select a Database Connection
- DestDataset_CSV2 = L:\Project9\TDAM Tijdelijke Opslag\Maarten   # Destination CSV (Comma Separated Value) Folder
- DestDataset_GEOPARQUET = K:\CentraalDatamanagement\PDC\01_WIP\01_Algemeen\X_000002_Datakwaliteit_Baseline   # Destination GeoParquet Folder

Writers:
- CSV2_1: CSV2 to $(DestDataset_CSV2)
- GEOPARQUET_1: GEOPARQUET to $(DestDataset_GEOPARQUET)

Note: PythonCreator: / SDE_bestand = FME_MacroValues['SDE_bestand'] / print(SDE_bestand) / arcpy.env.workspace = SDE_bestand / print(arcpy.env.workspace) / Tables = arcpy.ListFeatureClasses() / Tables += arcpy.ListTables() / ArchivedTables = [] / for i in Tables: / try: / desc = arcpy.Describe(i) / if desc.isArchived: / ArchivedTables.append(i) / except: / print("{} niet meegenomen".format(i)) / for i in ArchivedTables: / newFeature = fmeobjects.FMEFeature() / newFeature.setAttribute("table", i) / self.pyoutput(newFeature)
Note: Maakt een feature van alle tabellen in SDE-bestand met archiving
PythonCreator
    NEW_ATTRIBUTES = table char(200)
    PYTHONSOURCE_NEW:
      import fme
      from fme import BaseTransformer
      import fmeobjects
      import arcpy


      class FeatureCreator(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def input(self, feature: fmeobjects.FMEFeature):
              """This method is called once by FME to initiate feature creation.
              Any number of features can be created and emitted by the self.pyoutput() method.
              The initial feature argument is a placeholder and can be ignored.
              """
              SDE_bestand = FME_MacroValues['SDE_bestand']
              print(SDE_bestand)

              arcpy.env.workspace = SDE_bestand

              print(arcpy.env.workspace)

              Tables = arcpy.ListFeatureClasses()
              Tables += arcpy.ListTables()

              ArchivedTables = []

              for i in Tables:
                 try:
                    desc = arcpy.Describe(i)
                    if desc.isArchived:
                        ArchivedTables.append(i)
                 except:
                    print("{} niet meegenomen".format(i))

              for i in ArchivedTables:
                  newFeature = fmeobjects.FMEFeature()
                  newFeature.setAttribute("table", i)
      #            desc = arcpy.da.Describe(i)
      #            if 'shapeType' in desc.keys():
      #                newFeature.setAttribute("geometry_type", desc['shapeType'])
                  self.pyoutput(newFeature)

          def close(self):
              """This method is called at the end of the class."""
              pass
    PYTHONSYMBOL = FeatureCreator
    -> StringConcatenator
Note: Voegt _H toe aantebelnaam
StringConcatenator
    ACTION = Create New Attribute
    PARM_LINE = fme_basicstring:13%2:@Value(table)_H
    VAL_ATTR = HistoryTable
    -> FeatureReader [INITIATOR]

Bookmark: Oracle reader
FeatureReader
    ATTR_ACCUM_MODE = Only Use Result
    CLIP_TO_ENVELOPE = NO
    COMBINE_GEOM = Use Result
    DATASET = DAMOPRD_Oracle
    FEATURETYPES = @Value(HistoryTable)
    FORMAT = ORACLE_SPATIAL
    INITIATOR_FIRST_OUTPUT = default
    INTERACT = NONE
    ORACLE_SPATIAL_CHUNK_SIZE = 200
    ORACLE_SPATIAL_CREATE_FEATURE_TABLES_FROM_DATA = Yes
    ORACLE_SPATIAL_HANDLE_MULTIPLE_SPATIAL_COLUMNS = NO
    ORACLE_SPATIAL_NAMED_CONNECTION = DAMOPRD_Oracle
    ORACLE_SPATIAL_PARSE_MAPINFO_SYMBOLOGY = NO
    ORACLE_SPATIAL_PERSISTENT_CONNECTION = YES
    ORACLE_SPATIAL_QUERY_FEATURE_TYPES_FOR_MERGE_FILTERS = Yes
    ORACLE_SPATIAL_READ_3D_POLYGON_AS_FACE = NO
    ORACLE_SPATIAL_REMOVE_SCHEMA_QUALIFIER = NO
    ORACLE_SPATIAL_SERVER_TYPE = ORACLE8i
    ORACLE_SPATIAL_SHOW_SYSTEM_TABLES = NO
    ORACLE_SPATIAL_USE_SEARCH_ENVELOPE = NO
    ORACLE_SPATIAL_USE_UNIFIED_DATE_ATTRS = YES
    ORDER_RESULTS = No
    OUTPUT_ADD_SCHEMA_ATTRIBUTES = NO
    OUTPUT_FEATURES_DISPLAY = Schema and Data Features
    <SCHEMA> -> File1 (writer CSV2_1)
    <SCHEMA> -> geoparquet (writer GEOPARQUET_1)
    <OTHER> -> GeometryFilter
    <OTHER> -> geoparquet (writer GEOPARQUET_1)

Bookmark: Schrijven naar CSV
Note: filter null-geometriën
GeometryFilter
    FILTER_MODE = SIMPLE
    FILTER_MULTI = FILTER_TYPES]Null]FME_CONTROLLER_QUERY_FILE]]FME_CONTROLLER_CHOICE]Simple
    Null -> File1 (writer CSV2_1)
    <UNFILTERED> -> GeometryExtractor
Note: Zet geometrie om naar WKT
GeometryExtractor
    ATTR = Geometry
    KIND = wkt
    OGCVERSION = 1.2
    OGC_WKT_PRECISION = FLOAT_64
    REMOVE_GEOMETRY = No
    KIND_LONG = OGC Well Known Text
    OGC_WKT_PRECISION_DISPLAY = 64-bit
    -> File1 (writer CSV2_1)

Bookmark: New Bookmark
File1 (writer CSV2_1)
    attributes: Geometry string

Bookmark: Schrijven naar geoParquet
geoparquet (writer GEOPARQUET_1)
